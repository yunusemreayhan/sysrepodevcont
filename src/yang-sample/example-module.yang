module example-module {
  namespace "http://example.com/ns/example-module";
  prefix "ex";

  import ietf-yang-types {
    prefix yang;
  }

  container example-container {
    list example-list {
      key "name";
      unique "ip port";
      unique "name";
      leaf name {
        type string;
      }
      leaf value {
        type string;
      }
      leaf ip {
        type string;
      }
      leaf port {
        type int32;
      }
      list sub-list {
        key "name";
        leaf name {
          type string;
        }
        leaf value {
          type string;
        }
        list sub-sub-list {
          key "name";
          leaf name {
            type string;
          }
          leaf value {
            type string;
          }
        }
      }
    }
  }
}
